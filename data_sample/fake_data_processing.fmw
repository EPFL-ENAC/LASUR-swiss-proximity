FME workspace fake_data_processing.fmw

Parameters:
- SourceDataset_SHAPEFILE = $(FME_MF_DIR)swissBOUNDARIES3D_1_3_TLM_HOHEITSGEBIET.shp   # Source Esri Shapefile(s)
- SourceDataset_GEOJSON_5 = $(FME_MF_DIR)access_5th_transit.geojson   # Source GeoJSON File or URL
- SourceDataset_GEOJSON = $(FME_MF_DIR)access_5th_amenity.geojson   # Source GeoJSON File or URL

Readers:
- SHAPEFILE_1: SHAPEFILE from $(SourceDataset_SHAPEFILE)
- GEOJSON_1: GEOJSON from $(SourceDataset_GEOJSON)
- GEOJSON_2: GEOJSON from $(SourceDataset_GEOJSON_5)

swissBOUNDARIES3D_1_3_TLM_HOHEITSGEBIET (reader SHAPEFILE_1)
    attributes: UUID varchar(38), DATUM_AEND date, DATUM_ERST date, ERSTELL_J long, ERSTELL_M varchar(20), REVISION_J long, REVISION_M varchar(20), GRUND_AEND varchar(20), HERKUNFT varchar(20), HERKUNFT_J long, HERKUNFT_M varchar(20), OBJEKTART varchar(20), BEZIRKSNUM long, SEE_FLAECH number(31,15), REVISION_Q varchar(100), NAME varchar(254), KANTONSNUM long, ICC varchar(20), EINWOHNERZ long, BFS_NUMMER long, GEM_TEIL varchar(20), GEM_FLAECH number(31,15), SHN varchar(20)
    -> Tester
Tester
    BOOL_OP = OR
    TEST_CLAUSE = TEST @Value(KANTONSNUM) != 25
    TEST_MODE = TEST
    PASSED -> CsmapReprojector
CsmapReprojector
    DEST = EPSG:4326
    INTERPOLATION_TYPE_NAME = Nearest Neighbor
    RASTER_CELL_SIZE = Preserve Cells
    RASTER_TOLERANCE = 0.0
    SOURCE = CH1903Plus_1.LV95/01
    REPROJECTED -> Tiler
Tiler
    CLEANING_TOLERANCE = Automatic
    COLUMN_ATTR = _column
    DUPLICATE_ON_TILE_BORDERS = No
    INVALID_PART_HANDLING = REJECT_WHOLE_FEATURE
    MISSING_MEASURE_VALUES = Linear Interpolation
    MISSING_Z_VALUES = Planar Interpolation
    ROW_ATTR = _row
    STARTINGCORNER = Lower Left
    TILE_HEIGHT = 0.01
    TILE_WIDTH = 0.01
    TILING_TYPE = Tile Size
    TILED -> AttributeManager
AttributeManager
    ATTR_TABLE:
      REMOVE UUID
      REMOVE DATUM_AEND
      REMOVE DATUM_ERST
      REMOVE ERSTELL_J
      REMOVE ERSTELL_M
      REMOVE REVISION_J
      REMOVE REVISION_M
      REMOVE GRUND_AEND
      REMOVE HERKUNFT
      REMOVE HERKUNFT_J
      REMOVE HERKUNFT_M
      REMOVE OBJEKTART
      REMOVE BEZIRKSNUM
      REMOVE SEE_FLAECH
      REMOVE REVISION_Q
      RENAME_SET_VALUE NAME > COMMUNE
      REMOVE KANTONSNUM
      REMOVE ICC
      REMOVE EINWOHNERZ
      REMOVE BFS_NUMMER
      REMOVE GEM_TEIL
      REMOVE GEM_FLAECH
      REMOVE SHN
      REMOVE _column
      REMOVE _row
    -> RandomNumberGenerator
RandomNumberGenerator
    MAX = 2000
    MIN = 920
    PLACES = 0
    RESULT_ATTR = 5th_access_meter
    -> AttributeCreator
AttributeCreator
    ATTR_TABLE = SET_TO 5th_access_meter = @Evaluate(@Value(5th_access_meter)/10)
    -> RandomNumberGenerator_2
RandomNumberGenerator_2
    MAX = 4500072
    MIN = 100010
    PLACES = 0
    RESULT_ATTR = SSECTEUR_7
    -> AttributeRenamer
    -> AttributeRenamer_2
access_5th_transit (reader GEOJSON_2)
    attributes: SSECTEUR_7 string, 5th_access_meter float, COMMUNE string
    -> AttributeRenamer_2
AttributeRenamer_2
    ATTR_TABLE = RENAME_SET_DEFAULT 5th_access_meter > fifth_access_meter
    MISSING_INPUT_ATTRS = REMOVE
    -> AttributeRounder_2
AttributeRounder_2
    PLACES = 2
    ROUND_TYPE = Nearest
    SRC_ATTRS = fifth_access_meter
    -> MeasureRemover_2
MeasureRemover_2
    REMOVE_ALL = Yes
    -> CenterPointReplacer_2
    -> CsmapReprojector_5
    -> H3HexagonalIndexer_10
CsmapReprojector_5
    DEST = EPSG:3857
    INTERPOLATION_TYPE_NAME = Nearest Neighbor
    RASTER_CELL_SIZE = Preserve Cells
    RASTER_TOLERANCE = 0.0
    REPROJECTED -> FeatureWriter_13 [Output]
FeatureWriter_13
    DATASET = $(FME_MF_DIR_ENCODED)tileserv\access_5th_transit_11_13.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
CenterPointReplacer_2
    POINTTYPE = CENTER
    POINT -> H3HexagonalIndexer_4
H3HexagonalIndexer_4
    INDEX_OPERATION = Index
    -> StatisticsCalculator_2
StatisticsCalculator_2
    CALCULATION_MODE = NUMERIC
    FEAT_STATS = fifth_access_meter,NUMERIC_MODE,,,,,MEAN,,,,,,,,
    GROUP_BY = _h3index
    SUMMARY -> AttributeRenamer_5
AttributeRenamer_5
    ATTR_TABLE = RENAME_SET_DEFAULT fifth_access_meter.mean > fifth_access_meter
    MISSING_INPUT_ATTRS = REMOVE
    -> H3HexagonalIndexer_5
H3HexagonalIndexer_5
    INDEX_OPERATION = Hexagon From Index
    -> CsmapReprojector_6
CsmapReprojector_6
    DEST = EPSG:3857
    INTERPOLATION_TYPE_NAME = Nearest Neighbor
    RASTER_CELL_SIZE = Preserve Cells
    RASTER_TOLERANCE = 0.0
    SOURCE = EPSG:4326
    REPROJECTED -> FeatureWriter_14 [Output]
FeatureWriter_14
    DATASET = $(FME_MF_DIR_ENCODED)tileserv\access_5th_transit_9_10.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
H3HexagonalIndexer_10
    INDEX_OPERATION = Index
    -> StatisticsCalculator_5
StatisticsCalculator_5
    CALCULATION_MODE = NUMERIC
    FEAT_STATS = fifth_access_meter,NUMERIC_MODE,,,,,MEAN,,,,,,,,
    GROUP_BY = _h3index
    SUMMARY -> AttributeRenamer_7
AttributeRenamer_7
    ATTR_TABLE = RENAME_SET_DEFAULT fifth_access_meter.mean > fifth_access_meter
    MISSING_INPUT_ATTRS = REMOVE
    -> H3HexagonalIndexer_11
H3HexagonalIndexer_11
    INDEX_OPERATION = Hexagon From Index
    -> CsmapReprojector_8
CsmapReprojector_8
    DEST = EPSG:3857
    INTERPOLATION_TYPE_NAME = Nearest Neighbor
    RASTER_CELL_SIZE = Preserve Cells
    RASTER_TOLERANCE = 0.0
    SOURCE = EPSG:4326
    REPROJECTED -> FeatureWriter_15 [Output]
FeatureWriter_15
    DATASET = $(FME_MF_DIR_ENCODED)tileserv\access_5th_transit_0_8.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
access_5th_amenity (reader GEOJSON_1)
    attributes: SSECTEUR_7 string, 5th_access_meter float, COMMUNE string
    -> AttributeRenamer
AttributeRenamer
    ATTR_TABLE = RENAME_SET_DEFAULT 5th_access_meter > fifth_access_meter
    MISSING_INPUT_ATTRS = REMOVE
    -> AttributeRounder
AttributeRounder
    PLACES = 2
    ROUND_TYPE = Nearest
    SRC_ATTRS = fifth_access_meter
    -> MeasureRemover
MeasureRemover
    REMOVE_ALL = Yes
    -> CsmapReprojector_2
    -> CenterPointReplacer
CenterPointReplacer
    POINTTYPE = CENTER
    POINT -> H3HexagonalIndexer_2
    POINT -> H3HexagonalIndexer_6
H3HexagonalIndexer_6
    INDEX_OPERATION = Index
    -> StatisticsCalculator_3
StatisticsCalculator_3
    CALCULATION_MODE = NUMERIC
    FEAT_STATS = fifth_access_meter,NUMERIC_MODE,,,,,MEAN,,,,,,,,
    GROUP_BY = _h3index
    SUMMARY -> AttributeRenamer_4
AttributeRenamer_4
    ATTR_TABLE = RENAME_SET_DEFAULT fifth_access_meter.mean > fifth_access_meter
    MISSING_INPUT_ATTRS = REMOVE
    -> H3HexagonalIndexer_7
H3HexagonalIndexer_7
    INDEX_OPERATION = Hexagon From Index
    -> CsmapReprojector_3
CsmapReprojector_3
    DEST = EPSG:3857
    INTERPOLATION_TYPE_NAME = Nearest Neighbor
    RASTER_CELL_SIZE = Preserve Cells
    RASTER_TOLERANCE = 0.0
    SOURCE = EPSG:4326
    REPROJECTED -> FeatureWriter_10 [Output]
FeatureWriter_10
    DATASET = $(FME_MF_DIR_ENCODED)tileserv\access_5th_amenity_0_8.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
H3HexagonalIndexer_2
    INDEX_OPERATION = Index
    -> StatisticsCalculator
StatisticsCalculator
    CALCULATION_MODE = NUMERIC
    FEAT_STATS = fifth_access_meter,NUMERIC_MODE,,,,,MEAN,,,,,,,,
    GROUP_BY = _h3index
    SUMMARY -> AttributeRenamer_3
AttributeRenamer_3
    ATTR_TABLE = RENAME_SET_DEFAULT fifth_access_meter.mean > fifth_access_meter
    MISSING_INPUT_ATTRS = REMOVE
    -> H3HexagonalIndexer_3
H3HexagonalIndexer_3
    INDEX_OPERATION = Hexagon From Index
    -> CsmapReprojector_4
CsmapReprojector_4
    DEST = EPSG:3857
    INTERPOLATION_TYPE_NAME = Nearest Neighbor
    RASTER_CELL_SIZE = Preserve Cells
    RASTER_TOLERANCE = 0.0
    SOURCE = EPSG:4326
    REPROJECTED -> FeatureWriter_12 [Output]
FeatureWriter_12
    DATASET = $(FME_MF_DIR_ENCODED)tileserv\access_5th_amenity_9_10.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
CsmapReprojector_2
    DEST = EPSG:3857
    INTERPOLATION_TYPE_NAME = Nearest Neighbor
    RASTER_CELL_SIZE = Preserve Cells
    RASTER_TOLERANCE = 0.0
    REPROJECTED -> FeatureWriter_11 [Output]
FeatureWriter_11
    DATASET = $(FME_MF_DIR_ENCODED)tileserv\access_5th_amenity_11_13.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureWriter_9 [off]
    DATASET = $(FME_MF_DIR_ENCODED)access_5th_amenity_fake_data_switzerland_topojson.zip\access_5th_amenity_fake_data_switzerland.topojson
    DATASET_ATTR = _dataset
    FEATURE_TYPE_LIST_ATTR = _feature_types
    FORMAT = TOPOJSON
    TOPOJSON_COUNTER_CLOCKWISE_AREAS = Yes
    TOPOJSON_INDENT_SIZE = 0
    TOPOJSON_PRETTY_PRINT = YES
    TOPOJSON_QUANTIZE = 100000
    TOPOJSON_WGS84_REPROJECTION = Yes
    TOPOJSON_WRITE_BBOX = No
    TOTAL_FEATURES_WRITTEN_ATTR = _total_features_written
Junction_2
    -> FeatureWriter_2 [Output]
    -> FeatureWriter_4 [Output]
    -> Counter_2
Counter_2 [off]
    CNT_ATTR = _count
    DOMAIN = counter
    SCOPE = Global
    START = 0
    -> Aggregator_2 [off]
Aggregator_2 [off]
    ACCUM_ATTRS_NAME = Drop Incoming Attributes
    AGGREGATE_TYPE = Homogeneous Collection (If Possible)
    GROUP_BY = _count COMMUNE fifth_access_meter SSECTEUR_7
    MODE = Geometry - Assemble One Level
    SEP = ,
    AGGREGATE -> AttributeRemover_2 [off]
AttributeRemover_2 [off]
    REMOVE_ATTRS = _count
    -> FeatureWriter_8 [Output] [off]
    -> FeatureWriter_7 [Output] [off]
FeatureWriter_8 [off]
    DATASET = $(FME_MF_DIR_ENCODED)access_5th_transit_fake_data_switzerland_topojson_multi_parts.zip\access_5th_transit_fake_data_switzerland_multi_parts.topojson
    DATASET_ATTR = _dataset
    FEATURE_TYPE_LIST_ATTR = _feature_types
    FORMAT = TOPOJSON
    TOPOJSON_COUNTER_CLOCKWISE_AREAS = Yes
    TOPOJSON_PRETTY_PRINT = NO
    TOPOJSON_QUANTIZE = 100000
    TOPOJSON_WGS84_REPROJECTION = Yes
    TOPOJSON_WRITE_BBOX = No
    TOTAL_FEATURES_WRITTEN_ATTR = _total_features_written
FeatureWriter_7 [off]
    DATASET = $(FME_MF_DIR_ENCODED)access_5th_transit_fake_data_switzerland_multi_parts.zip\access_5th_transit_fake_data_switzerland_multi_parts.geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_MAX_COORDINATE_PRECISION = 10
    GEOJSON_PRETTY_PRINT = NO
    GEOJSON_WGS84_REPROJECTION = Yes
    GEOJSON_WRITER_CHARSET = UTF-8
    GEOJSON_WRITE_BOM = No
    TOTAL_FEATURES_WRITTEN_ATTR = _total_features_written
FeatureWriter_4 [off]
    DATASET = $(FME_MF_DIR_ENCODED)access_5th_transit_fake_data_switzerland_topojson.zip\access_5th_transit_fake_data_switzerland.topojson
    DATASET_ATTR = _dataset
    FEATURE_TYPE_LIST_ATTR = _feature_types
    FORMAT = TOPOJSON
    TOPOJSON_COUNTER_CLOCKWISE_AREAS = Yes
    TOPOJSON_PRETTY_PRINT = NO
    TOPOJSON_QUANTIZE = 100000
    TOPOJSON_WGS84_REPROJECTION = Yes
    TOPOJSON_WRITE_BBOX = No
    TOTAL_FEATURES_WRITTEN_ATTR = _total_features_written
FeatureWriter_2 [off]
    DATASET = $(FME_MF_DIR_ENCODED)access_5th_transit_fake_data_switzerland.zip\access_5th_transit_fake_data_switzerland.geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_MAX_COORDINATE_PRECISION = 10
    GEOJSON_PRETTY_PRINT = NO
    GEOJSON_WGS84_REPROJECTION = Yes
    GEOJSON_WRITER_CHARSET = UTF-8
    GEOJSON_WRITE_BOM = No
    TOTAL_FEATURES_WRITTEN_ATTR = _total_features_written
Junction [off]
    -> FeatureWriter_6 [Output] [off]
    -> FeatureWriter_5 [Output] [off]
    -> Counter [off]
FeatureWriter_6 [off]
    DATASET = $(FME_MF_DIR_ENCODED)access_5th_amenity_fake_data_switzerland_topojson.zip\access_5th_amenity_fake_data_switzerland.topojson
    DATASET_ATTR = _dataset
    FEATURE_TYPE_LIST_ATTR = _feature_types
    FORMAT = TOPOJSON
    TOPOJSON_COUNTER_CLOCKWISE_AREAS = Yes
    TOPOJSON_PRETTY_PRINT = NO
    TOPOJSON_QUANTIZE = 100000
    TOPOJSON_WGS84_REPROJECTION = Yes
    TOPOJSON_WRITE_BBOX = No
    TOTAL_FEATURES_WRITTEN_ATTR = _total_features_written
FeatureWriter_5 [off]
    DATASET = $(FME_MF_DIR_ENCODED)access_5th_amenity_fake_data_switzerland.zip\access_5th_amenity_fake_data_switzerland.geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_MAX_COORDINATE_PRECISION = 10
    GEOJSON_PRETTY_PRINT = NO
    GEOJSON_WGS84_REPROJECTION = Yes
    GEOJSON_WRITER_CHARSET = UTF-8
    GEOJSON_WRITE_BOM = No
    TOTAL_FEATURES_WRITTEN_ATTR = _total_features_written
Counter [off]
    CNT_ATTR = _count
    DOMAIN = counter
    SCOPE = Global
    START = 0
    -> Aggregator [off]
Aggregator [off]
    ACCUM_ATTRS_NAME = Drop Incoming Attributes
    AGGREGATE_TYPE = Homogeneous Collection (If Possible)
    GROUP_BY = _count COMMUNE fifth_access_meter SSECTEUR_7
    MODE = Geometry - Assemble One Level
    SEP = ,
    AGGREGATE -> AttributeRemover [off]
AttributeRemover [off]
    REMOVE_ATTRS = _count
    -> FeatureWriter [Output] [off]
    -> FeatureWriter_3 [Output] [off]
FeatureWriter_3 [off]
    DATASET = $(FME_MF_DIR_ENCODED)access_5th_amenity_fake_data_switzerland_topojson_multi_parts.zip\access_5th_amenity_fake_data_switzerland_multi_parts.topojson
    DATASET_ATTR = _dataset
    FEATURE_TYPE_LIST_ATTR = _feature_types
    FORMAT = TOPOJSON
    TOPOJSON_COUNTER_CLOCKWISE_AREAS = Yes
    TOPOJSON_PRETTY_PRINT = NO
    TOPOJSON_QUANTIZE = 100000
    TOPOJSON_WGS84_REPROJECTION = Yes
    TOPOJSON_WRITE_BBOX = No
    TOTAL_FEATURES_WRITTEN_ATTR = _total_features_written
FeatureWriter [off]
    DATASET = $(FME_MF_DIR_ENCODED)access_5th_amenity_fake_data_switzerland__multi_parts.zip\access_5th_amenity_fake_data_switzerland_multi_parts.geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_MAX_COORDINATE_PRECISION = 10
    GEOJSON_PRETTY_PRINT = NO
    GEOJSON_WGS84_REPROJECTION = Yes
    GEOJSON_WRITER_CHARSET = UTF-8
    GEOJSON_WRITE_BOM = No
    TOTAL_FEATURES_WRITTEN_ATTR = _total_features_written
