FME workspace process_tiles_and_hexagons.fmw

Parameters:
- OFFSET = 350   # Buffer Distance

Creator
    GEOMTYPE = Geometry Object
    NUM = 1
    CREATED -> FeatureReader [INITIATOR]
FeatureReader
    ATTRIBUTES = Verkehrszonen_NPVM_2017_agglo,"OBJECTID,GMDNR,CODE_ISO,GMDNAME,ACODE,ACAT,ANAME",ch.swisstopo.images-swissimage-dop10.metadata,"id,datenstand,resolution",dissolved_Agglo_Verkehrszonen_NPVM_2017_agglo,"ANAME,land_name",dissolved_Gem_Verkehrszonen_NPVM_2017_agglo,"OBJECTID,GMDNR,CODE_ISO,GMDNAME,ACODE,ACAT,ANAME",dissolved_Gem_Verkehrszonen_NVPM_2017,"GMDNR,GMDNAME",dissolved_Land_Verkehrszonen_Schweiz_NPVM_2017,dand_name,swissBOUNDARIES3D_1_3_TLM_HOHEITSGEBIET,"UUID,DATUM_AEND,DATUM_ERST,ERSTELL_J,ERSTELL_M,REVISION_J,REVISION_M,GRUND_AEND,HERKUNFT,HERKUNFT_J,HERKUNFT_M,OBJEKTART,BEZIRKSNUM,SEE_FLAECH,REVISION_Q,NAME,KANTONSNUM,ICC,EINWOHNERZ,BFS_NUMMER,GEM_TEIL,GEM_FLAECH,SHN"
    ATTR_ACCUM_MODE = Only Use Result
    COMBINE_GEOM = Use Result
    DATASET = ""$(FME_MF_DIR_ENCODED)source\ch.swisstopo.images-swissimage-dop10.metadata.shp" "$(FME_MF_DIR_ENCODED)source\dissolved_Agglo_Verkehrszonen_NPVM_2017_agglo.shp" "$(FME_MF_DIR_ENCODED)source\dissolved_Gem_Verkehrszonen_NPVM_2017_agglo.shp" "$(FME_MF_DIR_ENCODED)source\dissolved_Gem_Verkehrszonen_NVPM_2017.shp" "$(FME_MF_DIR_ENCODED)source\dissolved_Land_Verkehrszonen_Schweiz_NPVM_2017.shp" "$(FME_MF_DIR_ENCODED)source\swissBOUNDARIES3D_1_3_TLM_HOHEITSGEBIET.shp" "$(FME_MF_DIR_ENCODED)source\Verkehrszonen_NPVM_2017_agglo.shp""
    FORMAT = SHAPEFILE
    INTERACT = NONE
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    ch.swisstopo.images-swissimage-dop10.metadata -> Tiler_2
    dissolved_Agglo_Verkehrszonen_NPVM_2017_agglo -> Junction_3
    swissBOUNDARIES3D_1_3_TLM_HOHEITSGEBIET -> AttributeManager_5
Junction_3
    -> Junction
    -> Junction_4
Junction_4
    -> Junction_5
Junction_5
    -> CsmapReprojector_17
CsmapReprojector_17
    DEST = CH1903Plus_1.LV95/01
    INTERPOLATION_TYPE_NAME = Nearest Neighbor
    RASTER_CELL_SIZE = Preserve Cells
    RASTER_TOLERANCE = 0.0
    REPROJECTED -> AttributeManager_10
AttributeManager_10
    ATTR_TABLE:
      RENAME_SET_VALUE ANAME > agglomeration_name
      RENAME_SET_VALUE land_name > agglomeration_country
    USER_EXPOSED_ATTRIBUTES = _h3index
    -> AreaOnAreaOverlayer [AREA]
AreaOnAreaOverlayer
    ACCUM_ATTRS_NAME = Use Attributes From One Feature
    CLEANING_TOLERANCE = Automatic
    CONNECT_Z_MODE = First Wins
    DEAGGREGATE_INPUT = Yes
    LIST_ATTRS_TO_INCLUDE = agglomeration_country agglomeration_name
    LIST_NAME = agg
    OVC_ATTR = _overlaps
    AREA -> Counter_5
Counter_5
    CNT_ATTR = id_agglo
    SCOPE = Local
    START = 0
    -> ListConcatenator_5
    -> AttributeKeeper
ListConcatenator_5
    DROP_EMPTY_PARTS = No
    LIST_ATTR = agg{}.agglomeration_country
    SEP = ,
    VAL_ATTR = agglomeration_country
    -> ListConcatenator_6
ListConcatenator_6
    DROP_EMPTY_PARTS = No
    LIST_ATTR = agg{}.agglomeration_name
    SEP = ,
    VAL_ATTR = agglomeration_name
    -> FeatureMerger_3 [SUPPLIER]
AttributeKeeper
    CREATE_BULK_MODE_FEATURES = NO
    KEEP_ATTRS = id_agglo
    KEEP_LIST = agg{}.agglomeration_country agg{}.agglomeration_name
    -> AreaOnAreaOverlayer_4 [AREA]
AttributeManager_5
    ATTR_TABLE:
      REMOVE UUID
      REMOVE DATUM_AEND
      REMOVE DATUM_ERST
      REMOVE ERSTELL_J
      REMOVE ERSTELL_M
      REMOVE REVISION_J
      REMOVE REVISION_M
      REMOVE GRUND_AEND
      REMOVE HERKUNFT
      REMOVE HERKUNFT_J
      REMOVE HERKUNFT_M
      REMOVE OBJEKTART
      REMOVE BEZIRKSNUM
      REMOVE SEE_FLAECH
      REMOVE REVISION_Q
      RENAME_SET_VALUE NAME > municipality_name
      REMOVE KANTONSNUM
      REMOVE ICC
      REMOVE EINWOHNERZ
      RENAME_SET_VALUE BFS_NUMMER > ofs_no
      REMOVE GEM_TEIL
      REMOVE GEM_FLAECH
      REMOVE SHN
    -> Counter_7
Counter_7
    CNT_ATTR = id_c
    SCOPE = Local
    START = 0
    -> Clipper [CANDIDATE]
Creator_3
    GEOMTYPE = Geometry Object
    NUM = 1
    CREATED -> FeatureReader_3 [INITIATOR]
FeatureReader_3
    ATTRIBUTES = Verkehrszonen_Ausland_NPVM_2017,"ID_Zone,Name,NUTS2,NUTS3,NPVM2010,Ring,Kt_Herk,Kt_Zon_Nr,id"
    ATTR_ACCUM_MODE = Only Use Result
    COMBINE_GEOM = Use Result
    DATASET = $(FME_MF_DIR_ENCODED)source\Verkehrszonen_Ausland_NPVM_2017.gpkg
    FEATURETYPES = Verkehrszonen_Ausland_NPVM_2017
    FORMAT = OGCGEOPACKAGE
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    Verkehrszonen_Ausland_NPVM_2017 -> CsmapReprojector_16
CsmapReprojector_16
    DEST = CH1903Plus_1.LV95/01
    INTERPOLATION_TYPE_NAME = Nearest Neighbor
    RASTER_CELL_SIZE = Preserve Cells
    RASTER_TOLERANCE = 0.0
    REPROJECTED -> AreaCalculator_5
AreaCalculator_5
    AREA_ATTR = area_origin
    AREA_TYPE = Plane Area
    MULT = 1
    -> Counter_4
Counter_4
    CNT_ATTR = id_verkehrszonen
    SCOPE = Local
    START = 0
    -> AttributeKeeper_2
    -> AttributeKeeper_3
AttributeKeeper_2
    CREATE_BULK_MODE_FEATURES = NO
    KEEP_ATTRS = id_verkehrszonen,ID_Zone
    -> AreaOnAreaOverlayer_4 [AREA]
AreaOnAreaOverlayer_4
    ACCUM_ATTRS_NAME = Merge Incoming Attributes
    CLEANING_TOLERANCE = 0.1
    CONNECT_Z_MODE = First Wins
    DEAGGREGATE_INPUT = Yes
    OVC_ATTR = _overlaps
    AREA -> Tester_7
Tester_7
    BOOL_OP = COMPOSITE
    COMPOSITE_TEST = 1 AND 2
    TEST_CLAUSE:
      TEST id_agglo ATTRIBUTE_HAS_A_VALUE ""
      TEST id_verkehrszonen ATTRIBUTE_HAS_A_VALUE ""
    TEST_MODE = TEST
    PASSED -> FeatureMerger_3 [REQUESTOR]
FeatureMerger_3
    ATTR_ACCUM_MODE = Merge Supplier
    ATTR_CONFLICT_RES = Use Requestor
    IGNORE_NULLS = No
    JOIN_KEYS = @Value(id_agglo) @Value(id_agglo) AUTO
    MERGE_TYPE = Attributes Only
    PROCESS_DUPS = NO
    REJECT_NULL_MISSING_KEYS = No
    SUPPLIERS_FIRST = No
    MERGED -> Aggregator_5
Aggregator_5
    ACCUM_ATTRS_NAME = Drop Incoming Attributes
    AGGREGATE_TYPE = Homogeneous Collection (If Possible)
    CONCAT_ATTRS = agglomeration_country agglomeration_name
    GROUP_BY = id_verkehrszonen ID_Zone
    MODE = Geometry - Assemble One Level
    SEP = ,
    AGGREGATE -> PythonCaller
PythonCaller
    PYTHONSOURCE:
      import fme
      import fmeobjects

      import json


      class FeatureProcessor(object):
          """Template Class Interface:
          When using this class, make sure its name is set as the value of the 'Class
          to Process Features' transformer parameter.
          """

          def __init__(self):
              """Base constructor for class members."""
              pass

          def input(self, feature):


              agglomeration_country = feature.getAttribute('agglomeration_country')

              list_agglomeration_country = agglomeration_country.split(',')

              list_agglomeration_country_unique = list(set(list_agglomeration_country))
              feature.setAttribute('agglomeration_country',','.join(list_agglomeration_country_unique))



              agglomeration_name = feature.getAttribute('agglomeration_name')

              list_agglomeration_name = agglomeration_name.split(',')

              list_agglomeration_name_unique = list(set(list_agglomeration_name))
              feature.setAttribute('agglomeration_name',','.join(list_agglomeration_name_unique))




              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> FeatureMerger_4 [SUPPLIER]
AttributeKeeper_3
    CREATE_BULK_MODE_FEATURES = NO
    KEEP_ATTRS = id_verkehrszonen,Name,area_origin,Kt_Herk,ID_Zone
    -> FeatureMerger_4 [REQUESTOR]
FeatureMerger_4
    ATTR_ACCUM_MODE = Merge Supplier
    ATTR_CONFLICT_RES = Use Requestor
    IGNORE_NULLS = No
    JOIN_KEYS = @Value(id_verkehrszonen) @Value(id_verkehrszonen) AUTO
    MERGE_TYPE = Attributes Only
    PROCESS_DUPS = NO
    REJECT_NULL_MISSING_KEYS = No
    SUPPLIERS_FIRST = No
    MERGED -> AreaCalculator_6
AreaCalculator_6
    AREA_ATTR = area_final
    AREA_TYPE = Plane Area
    MULT = 1
    -> Tester_8
Tester_8
    BOOL_OP = OR
    TEST_CLAUSE = TEST @Value(area_final) > 1000
    TEST_MODE = TEST
    PASSED -> AttributeCreator_4
AttributeCreator_4
    ATTR_TABLE = SET_TO ration = @Evaluate(@Value(area_final)/@Value(area_origin))
    -> Tester_9
Tester_9
    BOOL_OP = OR
    TEST_CLAUSE = TEST @Value(ration) > 0.5
    TEST_MODE = TEST
    PASSED -> TestFilter
TestFilter
    DEFAULT_VALUE = in CH
    PASSED_TEST_GROUP_OUTPUT = FIRST
    TEST_LIST = "BOOL_OP,OR,COMPOSITE_TEST,""""""1"""""",TEST_CLAUSE,TEST Name ATTRIBUTE_HAS_A_VALUE """,out CH
    out CH -> Clipper_2 [CANDIDATE]
    in CH -> AttributeKeeper_4
AttributeKeeper_4
    CREATE_BULK_MODE_FEATURES = NO
    KEEP_ATTRS = agglomeration_country,agglomeration_name,ID_Zone
    -> Counter_6
Counter_6
    CNT_ATTR = id_v
    SCOPE = Local
    START = 0
    -> Clipper_3 [CANDIDATE]
Creator_2
    GEOMTYPE = Geometry Object
    NUM = 1
    CREATED -> FeatureReader_2 [INITIATOR]
Note: Lakes
FeatureReader_2
    ATTRIBUTES = stehende_gewaesser,"UUID,DATUM_AEND,DATUM_ERST,ERSTELL_J,ERSTELL_M,REVISION_J,REVISION_M,GRUND_AEND,HERKUNFT,HERKUNFT_J,HERKUNFT_M,OBJEKTART,REVISION_Q,id"
    ATTR_ACCUM_MODE = Only Use Result
    COMBINE_GEOM = Use Result
    DATASET = $(FME_MF_DIR_ENCODED)source\swissTLM3D_TLM_BODENBEDECKUNG.gpkg
    FEATURETYPES = stehende_gewaesser
    FORMAT = OGCGEOPACKAGE
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    stehende_gewaesser -> CsmapReprojector_12
    stehende_gewaesser -> SpatialFilter_4 [Filter]
    stehende_gewaesser -> Junction_6
CsmapReprojector_12
    DEST = EPSG:4326
    INTERPOLATION_TYPE_NAME = Nearest Neighbor
    RASTER_CELL_SIZE = Preserve Cells
    RASTER_TOLERANCE = 0.0
    REPROJECTED -> SpatialFilter_3 [Filter]
    REPROJECTED -> SpatialFilter_6 [Filter]
Junction_6
    -> Clipper [CLIPPER]
    -> Clipper_3 [CLIPPER]
    -> Clipper_2 [CLIPPER]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AreaOnAreaOverlayer_5 [AREA]
Clipper_3
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AreaCalculator_8
    OUTSIDE -> FeatureMerger_5 [REQUESTOR]
AreaCalculator_8
    AREA_ATTR = _area_init
    AREA_TYPE = Plane Area
    MULT = 1
    -> AreaOnAreaOverlayer_5 [AREA]
AreaOnAreaOverlayer_5
    ACCUM_ATTRS_NAME = Merge Incoming Attributes
    CLEANING_TOLERANCE = 0.1
    CONNECT_Z_MODE = First Wins
    DEAGGREGATE_INPUT = Yes
    OVC_ATTR = _overlaps
    AREA -> Tester_10
Tester_10
    BOOL_OP = AND
    TEST_CLAUSE:
      TEST id_c ATTRIBUTE_HAS_A_VALUE ""
      TEST id_v ATTRIBUTE_HAS_A_VALUE ""
    TEST_MODE = TEST
    PASSED -> AreaCalculator_7
AreaCalculator_7
    AREA_ATTR = _area
    AREA_TYPE = Plane Area
    MULT = 1
    -> AttributeCreator_5
AttributeCreator_5
    ATTR_TABLE = SET_TO ratio = @Evaluate(@Value(_area)/@Value(_area_init))
    -> Sorter
Sorter
    SORT_PARM = id_v NUMERIC ASCENDING ratio NUMERIC DESCENDING
    SORTED -> Aggregator_7
Aggregator_7
    ACCUM_ATTRS_NAME = Drop Incoming Attributes
    AGGREGATE_TYPE = Homogeneous Collection (If Possible)
    GROUP_BY = municipality_name id_v
    MODE = Geometry - Assemble One Level
    SEP = ,
    SUM = ratio
    AGGREGATE -> AttributeRounder
AttributeRounder
    PLACES = 2
    ROUND_TYPE = Nearest
    SRC_ATTRS = ratio
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(ratio) = 1",@Value(ratio) = 1,"BOOL_OP,OR,COMPOSITE_TEST,""""""1"""""",TEST_CLAUSE,TEST @Value(ratio) = 0",0
    @Value(ratio) = 1 -> AttributeCreator_8
    <UNFILTERED> -> AttributeCreator_7
AttributeCreator_8
    ATTR_TABLE = SET_TO Name = @Value(municipality_name)
    -> Junction_7
AttributeCreator_7
    ATTR_TABLE = SET_TO ratio = @Evaluate(@Value(ratio)*100)
    -> AttributeCreator_6
AttributeCreator_6
    ATTR_TABLE = SET_TO Name = @Value(municipality_name) (@Value(ratio)%)
    -> Aggregator_6
Aggregator_6
    ACCUM_ATTRS_NAME = Drop Incoming Attributes
    AGGREGATE_TYPE = Homogeneous Collection (If Possible)
    CONCAT_ATTRS = Name
    GROUP_BY = id_v
    MODE = Geometry - Assemble One Level
    SEP = ,
    AGGREGATE -> Junction_7
Junction_7
    -> AttributeKeeper_5
AttributeKeeper_5
    CREATE_BULK_MODE_FEATURES = NO
    KEEP_ATTRS = id_v,Name
    -> FeatureMerger_5 [SUPPLIER]
FeatureMerger_5
    ATTR_ACCUM_MODE = Merge Supplier
    ATTR_CONFLICT_RES = Use Requestor
    IGNORE_NULLS = No
    JOIN_KEYS = @Value(id_v) @Value(id_v) AUTO
    MERGE_TYPE = Attributes Only
    PROCESS_DUPS = NO
    REJECT_NULL_MISSING_KEYS = No
    SUPPLIERS_FIRST = No
    MERGED -> AttributeCreator_9
AttributeCreator_9
    ATTR_TABLE = SET_TO municipality_country = CH
    -> Junction_8
Clipper_2
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> AttributeCreator_10
AttributeCreator_10
    ATTR_TABLE = SET_TO municipality_country = @Value(Kt_Herk)
    -> Junction_8
Junction_8
    -> Sorter_2
Sorter_2
    SORT_PARM = Name NATURAL ASCENDING
    SORTED -> AttributeManager_11
AttributeManager_11
    ATTR_TABLE:
      REMOVE ration
      REMOVE area_origin
      REMOVE area_final
      REMOVE id_v
      REMOVE _clipped
      RENAME_SET_VALUE Name > municipality_name
      REMOVE id_verkehrszonen
      REMOVE Kt_Herk
      RENAME_SET_VALUE ID_Zone > id_zone
    -> CsmapReprojector_13
    -> FeatureWriter_8 [Reprojected00]
    -> CsmapReprojector_18
CsmapReprojector_13
    DEST = EPSG:4326
    INTERPOLATION_TYPE_NAME = Nearest Neighbor
    RASTER_CELL_SIZE = Preserve Cells
    RASTER_TOLERANCE = 0.0
    REPROJECTED -> FeatureWriter_4 [Output]
    REPROJECTED -> FeatureWriter_8 [Output]
    REPROJECTED -> Junction_9
Note: Lakes
Junction_9
    -> Dissolver_2
    -> SpatialRelator_3 [Supplier]
    -> CsmapReprojector_5
    -> SpatialRelator_2 [Supplier]
FeatureWriter_4
    DATASET = $(FME_MF_DIR_ENCODED)data\verkehrszonen_4326_geojson.zip\verkehrszonen__4326.json
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
FeatureWriter_8
    DATASET = $(FME_MF_DIR_ENCODED)data\verkehrszonen_geopackage.zip\verkehrszonen_.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written
CsmapReprojector_18
    DEST = EPSG:3857
    INTERPOLATION_TYPE_NAME = Nearest Neighbor
    RASTER_CELL_SIZE = Preserve Cells
    RASTER_TOLERANCE = 0.0

Bookmark: New Bookmark
Junction [off]
    -> Dissolver [off]
    -> SpatialRelator [Supplier] [off]
Note: Creation of h3 hexagons
Dissolver [off]
    ACCUM_INPUT_ATTRS = Use Attributes From One Feature
    CLEANING_TOLERANCE = Automatic
    CONNECT_Z_MODE = First Wins
    DEAGGREGATE_INPUT = Yes
    AREA -> Counter [off]
Counter [off]
    CNT_ATTR = polygon_id
    DOMAIN = counter
    SCOPE = Global
    START = 0
    -> CsmapReprojector [off]
    -> SpatialFilter [Filter] [off]
CsmapReprojector [off]
    DEST = EPSG:3857
    INTERPOLATION_TYPE_NAME = Nearest Neighbor
    RASTER_CELL_SIZE = Preserve Cells
    RASTER_TOLERANCE = 0.0
    SOURCE = EPSG:4326
    REPROJECTED -> Bufferer [off]
Bufferer [off]
    ANGLE = 22.5
    CAP_STYLE = Arc
    CORNER_STYLE = Arc
    MODE = AREA
    OFFSET = $(OFFSET)
    OFFSET_UNITS = NONE
    PRECISION = APPROX
    BUFFERED -> Tiler [off]
Tiler [off]
    CLEANING_TOLERANCE = Automatic
    COLUMN_ATTR = _column
    DUPLICATE_ON_TILE_BORDERS = No
    INVALID_PART_HANDLING = REJECT_WHOLE_FEATURE
    MISSING_MEASURE_VALUES = Linear Interpolation
    MISSING_Z_VALUES = Planar Interpolation
    ROW_ATTR = _row
    STARTINGCORNER = Lower Left
    TILE_HEIGHT = $(OFFSET)
    TILE_SEED_X = 0
    TILE_SEED_Y = 0
    TILE_WIDTH = $(OFFSET)
    TILING_TYPE = Tile Size
    TILED -> CenterPointReplacer [off]
CenterPointReplacer [off]
    POINTTYPE = CENTER
    POINT -> CsmapReprojector_2 [off]
CsmapReprojector_2 [off]
    DEST = EPSG:4326
    INTERPOLATION_TYPE_NAME = Nearest Neighbor
    RASTER_CELL_SIZE = Preserve Cells
    RASTER_TOLERANCE = 0.0
    SOURCE = EPSG:3857
    REPROJECTED -> H3HexagonalIndexer_6 [off]
H3HexagonalIndexer_6 [off]
    INDEX_OPERATION = Index
    -> DuplicateFilter [off]
DuplicateFilter [off]
    INPUT_ORDERED_CHOICE = No
    KEYATTR = _h3index
    UNIQUE -> H3HexagonalIndexer_8 [off]
H3HexagonalIndexer_8 [off]
    INDEX_OPERATION = Hexagon From Index
    -> SpatialFilter [Candidate] [off]
SpatialFilter [off]
    AGGREGATE_HANDLING = Yes
    ATTR_ACCUM_MODE = Merge Filter
    ATTR_CONFLICT_RES = Use Candidate
    BASE_TYPE = Multiple Filters
    CURVE_BOUNDARY_RULE_PARAM = Default Rule
    GROUP_BY = polygon_id
    PASS_CRITERIA = Pass Against One Filter
    PREDATTR = _predicate
    PREDICATES = INTERSECTS
    USE_BOUNDING_BOX = No
    PASSED -> AttributeManager [off]
AttributeManager [off]
    ATTR_TABLE:
      REMOVE ANAME
      REMOVE land_name
      REMOVE polygon_id
      REMOVE _column
      REMOVE _row
      REMOVE _predicate
    -> SpatialRelator [Requestor] [off]
SpatialRelator [off]
    AGGREGATE_HANDLING = Yes
    CALC_CARD = No
    CURVE_BOUNDARY_RULE_PARAM = Default Rule
    LIST_ATTRS_TO_INCLUDE = ANAME land_name
    LIST_NAME = _relationships
    PREDICATES = INTERSECTS
    SUCCESS_ATTR = _related_suppliers
    -> SpatialFilter_3 [Candidate] [off]
Note: remove the units totally included into a lake
SpatialFilter_3 [off]
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    FAILED -> ListElementCounter [off]
ListElementCounter [off]
    CNT_ATTR = _element_count
    LIST_NAME = _relationships{}
    -> ListConcatenator [off]
ListConcatenator [off]
    DROP_EMPTY_PARTS = No
    LIST_ATTR = _relationships{}.ANAME
    SEP = ,
    VAL_ATTR = agglomeration_name
    -> ListConcatenator_2 [off]
ListConcatenator_2 [off]
    DROP_EMPTY_PARTS = No
    LIST_ATTR = _relationships{}.land_name
    SEP = ,
    VAL_ATTR = agglomeration_country
    -> AttributeManager_2 [off]
AttributeManager_2 [off]
    ATTR_TABLE:
      RENAME_SET_VALUE _h3index > h3index
      REMOVE _relationships{}.ANAME
      REMOVE _relationships{}.land_name
      REMOVE _relationships{}.de9im
      REMOVE _relationships{}.pass{}
      REMOVE _related_suppliers
      REMOVE _element_count
    -> CsmapReprojector_3 [off]
    -> FeatureWriter [Output] [off]
    -> CsmapReprojector_4 [off]
    -> FeatureWriter_2 [Output] [off]
FeatureWriter_2 [off]
    DATASET = $(FME_MF_DIR_ENCODED)data\h3_agglomeration_4326_geojson.zip\h3_agglomeration_4326.json
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
CsmapReprojector_3 [off]
    DEST = EPSG:3857
    INTERPOLATION_TYPE_NAME = Nearest Neighbor
    RASTER_CELL_SIZE = Preserve Cells
    RASTER_TOLERANCE = 0.0
    REPROJECTED -> FeatureWriter [Reprojected] [off]
CsmapReprojector_4 [off]
    DEST = EPSG:2056
    INTERPOLATION_TYPE_NAME = Nearest Neighbor
    RASTER_CELL_SIZE = Preserve Cells
    RASTER_TOLERANCE = 0.0
    REPROJECTED -> FeatureWriter [Reprojected00] [off]
FeatureWriter [off]
    DATASET = $(FME_MF_DIR_ENCODED)data\h3_agglomeration_geopackage.zip\h3_agglomeration.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written

Bookmark: New Bookmark
Note: Creation of square tiles
Tiler_2
    CLEANING_TOLERANCE = Automatic
    COLUMN_ATTR = _column
    DUPLICATE_ON_TILE_BORDERS = No
    GROUP_BY = id
    INVALID_PART_HANDLING = REJECT_WHOLE_FEATURE
    MISSING_MEASURE_VALUES = Linear Interpolation
    MISSING_Z_VALUES = Planar Interpolation
    NUM_HORIZONTAL_TILES = 2
    NUM_VERTICAL_TILES = 2
    ROW_ATTR = _row
    STARTINGCORNER = Lower Left
    TILING_TYPE = Number of Tiles
    TILED -> AttributeCreator
AttributeCreator
    ATTR_TABLE = SET_TO index = @Value(id)_@Value(_row)_@Value(_column)
    -> SpatialFilter_2 [Candidate]
CsmapReprojector_5
    DEST = CH1903Plus_1.LV95/01
    INTERPOLATION_TYPE_NAME = Nearest Neighbor
    RASTER_CELL_SIZE = Preserve Cells
    RASTER_TOLERANCE = 0.0
    REPROJECTED -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialRelator_2 [Requestor]
SpatialRelator_2
    AGGREGATE_HANDLING = Yes
    CALC_CARD = No
    CURVE_BOUNDARY_RULE_PARAM = Default Rule
    LIST_ATTRS_TO_INCLUDE = municipality_country municipality_name
    LIST_NAME = _relationships
    PREDICATES = INTERSECTS
    SUCCESS_ATTR = _related_suppliers
    -> ListElementCounter_2
ListElementCounter_2
    CNT_ATTR = _element_count
    LIST_NAME = _relationships{}
    -> ListConcatenator_3
ListConcatenator_3
    DROP_EMPTY_PARTS = No
    LIST_ATTR = _relationships{}.municipality_name
    SEP = ,
    VAL_ATTR = agglomeration_name
    -> ListConcatenator_4
ListConcatenator_4
    DROP_EMPTY_PARTS = No
    LIST_ATTR = _relationships{}.municipality_country
    SEP = ,
    VAL_ATTR = agglomeration_country
    -> AttributeManager_3
AttributeManager_3
    ATTR_TABLE:
      REMOVE _relationships{}.de9im
      REMOVE _relationships{}.pass{}
      REMOVE _related_suppliers
      REMOVE _element_count
      REMOVE id
      REMOVE datenstand
      REMOVE resolution
      REMOVE _column
      REMOVE _row
      REMOVE _predicate
    USER_EXPOSED_ATTRIBUTES = _h3index
    -> SpatialFilter_4 [Candidate]
Note: remove the units totally included into a lake
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    FAILED -> Junction_2
Junction_2
    -> CsmapReprojector_7
    -> FeatureWriter_5 [Reprojected00]
CsmapReprojector_7
    DEST = EPSG:4326
    INTERPOLATION_TYPE_NAME = Nearest Neighbor
    RASTER_CELL_SIZE = Preserve Cells
    RASTER_TOLERANCE = 0.0
    SOURCE = CH1903Plus_1.LV95/01
    REPROJECTED -> FeatureWriter_3 [Output]
    REPROJECTED -> FeatureWriter_5 [Output]
FeatureWriter_3
    DATASET = $(FME_MF_DIR_ENCODED)data\tile_agglomeration_4326_geojson.zip\tile_agglomeration_4326.json
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
FeatureWriter_5
    DATASET = $(FME_MF_DIR_ENCODED)data\tile_agglomeration_geopackage.zip\tile_agglomeration.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written

Bookmark: New Bookmark
Note: Creation of h3 hexagons
Dissolver_2
    ACCUM_INPUT_ATTRS = Use Attributes From One Feature
    CLEANING_TOLERANCE = Automatic
    CONNECT_Z_MODE = First Wins
    DEAGGREGATE_INPUT = Yes
    AREA -> Counter_2
Counter_2
    CNT_ATTR = polygon_id
    DOMAIN = counter
    SCOPE = Global
    START = 0
    -> CsmapReprojector_9
    -> SpatialFilter_5 [Filter]
CsmapReprojector_9
    DEST = EPSG:3857
    INTERPOLATION_TYPE_NAME = Nearest Neighbor
    RASTER_CELL_SIZE = Preserve Cells
    RASTER_TOLERANCE = 0.0
    SOURCE = EPSG:4326
    REPROJECTED -> Bufferer_2
Bufferer_2
    ANGLE = 22.5
    CAP_STYLE = Arc
    CORNER_STYLE = Arc
    MODE = AREA
    OFFSET = $(OFFSET)
    OFFSET_UNITS = NONE
    PRECISION = APPROX
    BUFFERED -> Tiler_3
Tiler_3
    CLEANING_TOLERANCE = Automatic
    COLUMN_ATTR = _column
    DUPLICATE_ON_TILE_BORDERS = No
    INVALID_PART_HANDLING = REJECT_WHOLE_FEATURE
    MISSING_MEASURE_VALUES = Linear Interpolation
    MISSING_Z_VALUES = Planar Interpolation
    ROW_ATTR = _row
    STARTINGCORNER = Lower Left
    TILE_HEIGHT = $(OFFSET)
    TILE_SEED_X = 0
    TILE_SEED_Y = 0
    TILE_WIDTH = $(OFFSET)
    TILING_TYPE = Tile Size
    TILED -> CenterPointReplacer_2
CenterPointReplacer_2
    POINTTYPE = CENTER
    POINT -> CsmapReprojector_10
CsmapReprojector_10
    DEST = EPSG:4326
    INTERPOLATION_TYPE_NAME = Nearest Neighbor
    RASTER_CELL_SIZE = Preserve Cells
    RASTER_TOLERANCE = 0.0
    SOURCE = EPSG:3857
    REPROJECTED -> H3HexagonalIndexer_2
H3HexagonalIndexer_2
    INDEX_OPERATION = Index
    -> DuplicateFilter_2
DuplicateFilter_2
    INPUT_ORDERED_CHOICE = No
    KEYATTR = _h3index
    UNIQUE -> H3HexagonalIndexer_3
H3HexagonalIndexer_3
    INDEX_OPERATION = Hexagon From Index
    -> SpatialFilter_5 [Candidate]
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeManager_4
AttributeManager_4
    ATTR_TABLE:
      REMOVE polygon_id
      REMOVE _column
      REMOVE _row
      REMOVE _predicate
    -> SpatialRelator_3 [Requestor]
SpatialRelator_3
    AGGREGATE_HANDLING = Yes
    CALC_CARD = No
    CURVE_BOUNDARY_RULE_PARAM = Default Rule
    LIST_ATTRS_TO_INCLUDE = agglomeration_country agglomeration_name municipality_country municipality_name
    LIST_NAME = _relationships
    PREDICATES = INTERSECTS
    SUCCESS_ATTR = _related_suppliers
    -> SpatialFilter_6 [Candidate]
Note: remove the units totally included into a lake
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    FAILED -> ListElementCounter_3
ListElementCounter_3
    CNT_ATTR = _element_count
    LIST_NAME = _relationships{}
    -> ListConcatenator_7
ListConcatenator_7
    DROP_EMPTY_PARTS = No
    LIST_ATTR = _relationships{}.agglomeration_name
    SEP = ,
    VAL_ATTR = agglomeration_name
    -> ListConcatenator_8
ListConcatenator_8
    DROP_EMPTY_PARTS = No
    LIST_ATTR = _relationships{}.agglomeration_country
    SEP = ,
    VAL_ATTR = agglomeration_country
    -> AttributeManager_6
AttributeManager_6
    ATTR_TABLE:
      RENAME_SET_VALUE _h3index > h3index
      REMOVE _relationships{}.de9im
      REMOVE _relationships{}.pass{}
      REMOVE _related_suppliers
      REMOVE _element_count
    -> FeatureWriter_6 [Output]
    -> CsmapReprojector_14
    -> FeatureWriter_7 [Output]
FeatureWriter_7
    DATASET = $(FME_MF_DIR_ENCODED)data\h3_agglomeration_4326_geojson.zip\h3_agglomeration_4326.json
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
CsmapReprojector_14
    DEST = EPSG:2056
    INTERPOLATION_TYPE_NAME = Nearest Neighbor
    RASTER_CELL_SIZE = Preserve Cells
    RASTER_TOLERANCE = 0.0
    REPROJECTED -> FeatureWriter_6 [Reprojected00]
FeatureWriter_6
    DATASET = $(FME_MF_DIR_ENCODED)data\h3_agglomeration_geopackage.zip\h3_agglomeration.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written
