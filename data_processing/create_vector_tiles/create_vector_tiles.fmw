FME workspace create_vector_tiles.fmw

Creator
    GEOMTYPE = Geometry Object
    NUM = 1
    CREATED -> FeatureReader [INITIATOR]
    CREATED -> FeatureReader_2 [INITIATOR]
Note: read h3
FeatureReader
    ATTRIBUTES = h3_2056,"h3index,agglomeration_name,agglomeration_country,municipality_name,municipality_country,_relationships.agglomeration_name,_relationships.agglomeration_country,_relationships.municipality_name,_relationships.municipality_country,id",h3_4326,"h3index,agglomeration_name,agglomeration_country,municipality_name,municipality_country,_relationships.agglomeration_name,_relationships.agglomeration_country,_relationships.municipality_name,_relationships.municipality_country,id"
    ATTR_ACCUM_MODE = Only Use Result
    COMBINE_GEOM = Use Result
    DATASET = C:\projects\LASUR-rhytmic-mobility-habits\data_processing\create_processing_units\data\h3_agglomeration_geopackage.zip
    FEATURETYPES = h3_2056
    FORMAT = OGCGEOPACKAGE
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    h3_2056 -> CsmapReprojector
CsmapReprojector
    DEST = EPSG:3857
    INTERPOLATION_TYPE_NAME = Nearest Neighbor
    RASTER_CELL_SIZE = Preserve Cells
    RASTER_TOLERANCE = 0.0
    REPROJECTED -> PythonCaller
PythonCaller
    NEW_ATTRIBUTES = bike_barsresaurants bike_barsresaurants bike_health bike_posts bike_schools bike_transit fme_feature_type fme_geometry fme_type geopackage_type h3index id transit_barsresaurants transit_health transit_posts transit_schools transit_transit walk_barsresaurants walk_health walk_posts walk_schools walk_transit
    PYTHONSOURCE:
      import fme
      import fmeobjects
      import random



      class FeatureProcessor(object):
          """Template Class Interface:
          When using this class, make sure its name is set as the value of the 'Class
          to Process Features' transformer parameter.
          """

          def __init__(self):
              """Base constructor for class members."""
              pass

          def input(self, feature):

              list_attribute = ['posts','schools','barsresaurants','health','transit']
              list_transport = ['walk','bike','transit']


              for i in list_transport :
                  for j in list_attribute :
                      attribute_name = f"{i}_{j}"
                      attribute_value = random.randint(0, 3000)
                      feature.setAttribute(attribute_name, attribute_value)








              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> Junction
    -> H3HexagonalIndexer_2
    -> H3HexagonalIndexer
H3HexagonalIndexer
    INDEX_OPERATION = Parent Index
    -> DuplicateFilter
DuplicateFilter
    INPUT_ORDERED_CHOICE = No
    KEYATTR = _parentIndex
    UNIQUE -> CsmapReprojector_2
Note: 7
CsmapReprojector_2
    DEST = EPSG:3857
    INTERPOLATION_TYPE_NAME = Nearest Neighbor
    RASTER_CELL_SIZE = Preserve Cells
    RASTER_TOLERANCE = 0.0
    SOURCE = EPSG:4326
    REPROJECTED -> FeatureWriter_2 [Output]
FeatureWriter_2
    DATASET = $(FME_MF_DIR_ENCODED)output\h3\low.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
H3HexagonalIndexer_2
    INDEX_OPERATION = Parent Index
    -> DuplicateFilter_2
DuplicateFilter_2
    INPUT_ORDERED_CHOICE = No
    KEYATTR = _parentIndex
    UNIQUE -> CsmapReprojector_3
Note: 8
CsmapReprojector_3
    DEST = EPSG:3857
    INTERPOLATION_TYPE_NAME = Nearest Neighbor
    RASTER_CELL_SIZE = Preserve Cells
    RASTER_TOLERANCE = 0.0
    SOURCE = EPSG:4326
    REPROJECTED -> FeatureWriter_5 [Output]
FeatureWriter_5
    DATASET = $(FME_MF_DIR_ENCODED)output\h3\medium.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
Note: 9
Junction
    -> FeatureWriter_6 [Output]
FeatureWriter_6
    DATASET = $(FME_MF_DIR_ENCODED)output\h3\hight.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureReader_2
    ATTRIBUTES = municipalities_2056,"municipality_name,ofs_no,agglomeration_name,agglomeration_country,id",municipalities_3857,"municipality_name,ofs_no,agglomeration_name,agglomeration_country,id",municipalities_4326,"municipality_name,ofs_no,agglomeration_name,agglomeration_country,id"
    ATTR_ACCUM_MODE = Only Use Result
    COMBINE_GEOM = Use Result
    DATASET = C:\projects\LASUR-rhytmic-mobility-habits\data_processing\create_processing_units\data\municipalities_geopackage.zip
    FEATURETYPES = municipalities_3857
    FORMAT = OGCGEOPACKAGE
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    municipalities_3857 -> PythonCaller_2
PythonCaller_2
    NEW_ATTRIBUTES = bike_barsresaurants bike_barsresaurants bike_health bike_posts bike_schools bike_transit fme_feature_type fme_geometry fme_type geopackage_type h3index id transit_barsresaurants transit_health transit_posts transit_schools transit_transit walk_barsresaurants walk_health walk_posts walk_schools walk_transit
    PYTHONSOURCE:
      import fme
      import fmeobjects
      import random



      class FeatureProcessor(object):
          """Template Class Interface:
          When using this class, make sure its name is set as the value of the 'Class
          to Process Features' transformer parameter.
          """

          def __init__(self):
              """Base constructor for class members."""
              pass

          def input(self, feature):

              list_attribute = ['posts','schools','barsresaurants','health','transit']
              list_transport = ['walk','bike','transit']


              for i in list_transport :
                  for j in list_attribute :
                      attribute_name = f"{i}_{j}"
                      attribute_value = random.randint(0, 3000)
                      feature.setAttribute(attribute_name, attribute_value)








              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> FeatureWriter_12 [Output00]
FeatureWriter_12
    DATASET = $(FME_MF_DIR_ENCODED)output\access_5th_0_8.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureWriter_4
    DATASET = $(FME_MF_DIR_ENCODED)output\access_5th_0_8.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureWriter_3
    DATASET = $(FME_MF_DIR_ENCODED)output\access_5th_9_10.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
